;automatically create new dimension style
(defun c:jeff ()
    (setvar "DIMCLRD" "ByBlock")
    (setvar "DIMALTD" 4)
    (setvar "DIMALTF" 1)
    (setvar "DIMALTTD" 4)
    (setvar "DIMALTU" 4)
    (setvar "DIMADEC" 1)
    (setvar "DIMAZIN" 0)
    (setvar "DIMARCSYM" 1)
    (setvar "DIMASZ" 1)
    (setvar "DIMCEN" 0)
    (setvar "DIMCLRD" 3)
    (setvar "DIMDLE" 0)
    (setvar "DIMLWD" -2)
    (setvar "DIMDLI" 4)
    (setvar "DIMCLRE" 3)
    (setvar "DIMEXE" 0.5)
    (setvar "DIMLWE" -2)
    (setvar "DIMEXO" 0.75)
    (setvar "DIMFRAC" 0)
    (setvar "DIMLUNIT" 5)
    (setvar "DIMSCALE" 1)
    (setvar "DIMRND" 0)
    (setvar "DIMCLRT" 3)
    (setvar "DIMTXT" 1.5)
    (setvar "DIMGAP" 0.1)
    (setvar "DIMTAD" 0)
    (setvar "DIMTM" 0)
    (setvar "DIMTP" 0)
    (setvar "DIMTFAC" 1)
    (setvar "DIMTZIN" 0)
    (setvar "DIMZIN" 0)

    (command "dimstyle" "s" "Jeff50")

    (princ)
)
