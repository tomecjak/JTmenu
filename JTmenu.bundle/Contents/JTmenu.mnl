;=========================================================================
; JTmenu.mnl
; Create by Jakub Tomecko
;
; Autoload pre JTmenu
;-------------------------------------------------------------------------

;;----------------------------------------------------------------------;;
;;                  Zdielana kniznica (nacitana ako prva)               ;;
;;----------------------------------------------------------------------;;
;; Obsahuje spolocne pomocne funkcie (LM:acdoc, LM:startundo, LM:endundo,
;; LM:roundm, JT:BlockScale, JT:SignScale), ktore vyuzivaju ostatne moduly
(load "JTmenu_lib" "\nJTmenu_lib nenacitany!")
(princ)

;;----------------------------------------------------------------------;;
;;                                Commands                              ;;
;;----------------------------------------------------------------------;;
;; Obsahuje prikazy pre nastavenie globalnych premennych
(AUTOLOAD "JTmenu_commands" '("JTBlockScaleVar"))
(AUTOLOAD "JTmenu_commands" '("JTPreviewMode"))
(AUTOLOAD "JTmenu_commands" '("JTToolPaletteImportInfo"))
(princ)

;;----------------------------------------------------------------------;;
;;                               Funkcie                                ;;
;;----------------------------------------------------------------------;;
;; Obsahuje rozne funkcie v ramci JTmenu
(AUTOLOAD "Cadastre" '("JTCadastre"))
(AUTOLOAD "Maps" '("JTMaps"))
(AUTOLOAD "Road_maps" '("JTRoadMaps"))
(AUTOLOAD "Rebar_scheme" '("JTRebarScheme"))
(AUTOLOAD "Create_layers" '("JTCreateLayers"))
(AUTOLOAD "Block_base_point" '("JTBlockBasePoint"))
(AUTOLOAD "Center_measure" '("JTCenterMeasure"))
(AUTOLOAD "Viewport_outline" '("JTViewportOutline"))
(AUTOLOAD "Object_break" '("JTObjectBreak"))
(AUTOLOAD "Double_offset" '("JTDoubleOffset"))
(AUTOLOAD "Rename_block" '("JTRenameBlock"))
(AUTOLOAD "Stationing" '("JTStationing"))
(AUTOLOAD "North_arrow" '("JTNorthArrow"))
(AUTOLOAD "Coordinates_symbol" '("JTCoordinates"))
(AUTOLOAD "Help" '("JTHelp"))
(AUTOLOAD "Bugs_report" '("JTBugsReport"))
(AUTOLOAD "Create_dimensions" '("JTCreateDimensions"))
(AUTOLOAD "Text_style" '("JTTextStyle"))
(AUTOLOAD "Multileader_style" '("JTMultileader"))
(AUTOLOAD "Setting" '("JTsetting"))
(AUTOLOAD "Networks" '("JTNetworks"))
(AUTOLOAD "Layout_functions" '("JTTitleBlock" "JTSheetCross" "JTTitleBlockUpdate"))
(AUTOLOAD "Rebar_length" '("JTRebarLength"))
(AUTOLOAD "Material_update" '("JTMaterialUpdate" "JTConcreteHelp" "JTSteelHelp"))
(AUTOLOAD "Zone_update" '("JTZoneUpdate"))
(AUTOLOAD "Slope" '("JTSlope"))
(AUTOLOAD "Template_units" '("JTTemplateUnits"))
(AUTOLOAD "Folders_scheme" '("JTFolder"))
(AUTOLOAD "Prefix_layers" '("JTLayerPrexifRename"))
(AUTOLOAD "VerticalLine" '("JTVerticalLine"))
(AUTOLOAD "Select_by_layer" '("JTSelectbylayer"))
(AUTOLOAD "Measurement" '("JTMeasurement"))
(AUTOLOAD "Block_renumber" '("JTReNumber"))
(AUTOLOAD "Polyline_export" '("JTPolylineExport"))
(AUTOLOAD "Create_polyline" '("JTCreatePolyline"))
(AUTOLOAD "Drainage" '("JTDrainage"))
(AUTOLOAD "Hydrotechnical_calculation" '("JTHydrotechnical"))
(AUTOLOAD "Oblique_dimension" '("JTDimOblique"))
(AUTOLOAD "Curve_dimension" '("JTCurveDimension"))
(princ)

;;----------------------------------------------------------------------;;
;;                           Funkcie vystuze                            ;;
;;----------------------------------------------------------------------;;
;; Obsahuje funkcie pre vystuzovanie v ramci JTmenu
(AUTOLOAD "Rebar_function_orchester" '("JTRebarFillet" "JTRebarWrite" "JTRebarOffset"))
(AUTOLOAD "Rebar_functions" '("JTRebarIntersect" "JTRebarFilletPolyline" "JTRebarWritePolyline" "JTRebarLayers" "JTRebarOffsetPolyline" "JTRebarTagExport"))
(AUTOLOAD "Rebar_functions_layer" '("JTRebarFilletLayer" "JTRebarWriteLayer" "JTRebarOffsetLayer"))
(AUTOLOAD "Rebar_dimension" '("JTRebarDimension"))
(AUTOLOAD "Rebar_layers_manager" '("JTRebarLayerManager"))
(princ)

;;----------------------------------------------------------------------;;
;;                              Dokumentacia                            ;;
;;----------------------------------------------------------------------;;
(AUTOLOAD "Technical_documents" '("VL01"))
(AUTOLOAD "Technical_documents" '("VL01_1"))
(AUTOLOAD "Technical_documents" '("VL022"))
(AUTOLOAD "Technical_documents" '("VL04"))
(AUTOLOAD "Technical_documents" '("VL04_1"))
(AUTOLOAD "Technical_documents" '("VL05"))
(AUTOLOAD "Technical_documents" '("VL061T"))
(AUTOLOAD "Technical_documents" '("VL061V"))
(AUTOLOAD "Technical_documents" '("VL062T"))
(AUTOLOAD "Technical_documents" '("VL062V"))
(AUTOLOAD "Technical_documents" '("VL063T"))
(AUTOLOAD "Technical_documents" '("VL063V"))
(AUTOLOAD "Technical_documents" '("VL064T"))
(AUTOLOAD "Technical_documents" '("VL064V"))
(AUTOLOAD "Technical_documents" '("VL10"))
(AUTOLOAD "Technical_documents" '("JTTP"))
(AUTOLOAD "Technical_documents" '("JTZK25"))
(AUTOLOAD "Technical_documents" '("JTVL59"))
(AUTOLOAD "Technical_documents" '("JTVL60"))
(AUTOLOAD "Technical_documents" '("TPSK"))
(AUTOLOAD "Technical_documents" '("TPCZ"))
(princ)

;;----------------------------------------------------------------------;;
;;                    Nastroje dopravne znacenia                        ;;
;;----------------------------------------------------------------------;;
(AUTOLOAD "Traffic_signs_tools" '("JTTrafficSignsCanceled"))
(AUTOLOAD "Traffic_signs_tools" '("JTTrafficSignsScale"))
(princ)

;;----------------------------------------------------------------------;;
;;     Kniznica blokov dopravneho znacenia (nove+jestv.+vodorovne)      ;;
;;----------------------------------------------------------------------;;
;; Prikazy DZxxx a DZxxx_J sa generuju datovo priamo v tychto suboroch,
;; preto sa nacitavaju rovno (uz nie cez stovky AUTOLOAD riadkov).
(load "Traffic_signs" "\nTraffic_signs nenacitany!")
(load "Traffic_signs_existing" "\nTraffic_signs_existing nenacitany!")
(load "Traffic_signs_horizontal" "\nTraffic_signs_horizontal nenacitany!")
(load "Traffic_line" "\nTraffic_line nenacitany!")
(princ)

;;----------------------------------------------------------------------;;
;;                              Bloky symbolov                          ;;
;;----------------------------------------------------------------------;;
(AUTOLOAD "Inserting_blocks" '("JTDirection" "JTDirection2" "JTWaterDirection" "JTViewName" "JTSectionVertical" 
                               "JTSectionHorizontal" "JTSectionBreak" "JTAlignedText" "JTSlopeSymbol" 
                               "JTAxisSymbol" "JTTabMaterial" "JTTabBends" "JTNote" "JTProtectionZone"
                               "JTRebar" "JTRebarClip" "JTRebarClip2" "JTRebarDescription" "JTRebarMark" "JTPointBlock" "JTPointHeight"
                               "JTHectometricNetwork" "JTHeightTable" "JTDotText" "JTBearingSymbol"
                               "JTGeodeticMark" "JTSymmetry" "JTDetailSymbol" "JTCylinderEnd")
)
(princ)

;;----------------------------------------------------------------------;;
;;         Nastavenie globalnych parametrov ak este neexistuju          ;;
;;----------------------------------------------------------------------;;

(if (= (getenv "GlobalnaHladinaBlokov") nil)
  ;nastavenie hladinu na DP_Popis
  (setenv "GlobalnaHladinaBlokov" "0")
)

(if (= (getenv "GlobalnaKotyDIMSCALEset") nil)
  ;nastavenie modu kot na klasicky
  (setenv "GlobalnaKotyDIMSCALEset" "Klasicky")
)

(if (= (getenv "GlobalnyFormatCislaVykresu") nil)
  ;nastavenie formatu cislovanie vykresu na 2
  (setenv "GlobalnyFormatCislaVykresu" "0")
)

(if (= (getenv "GlobalneVyhotovilVykres") nil)
  ;nastavenie mena vyhotovil na hodnotu menu
  (setenv "GlobalneVyhotovilVykres" "Meno")
)

(if (= (getenv "GlobalnaPrefixHladiny") nil)
  ;nastavenie nazvu prefixu hlafiny
  (setenv "GlobalnaPrefixHladiny" "DP")
)

(if (= (getenv "GlobalnaPrefixHladinySeparator") nil)
  ;nastavenie nazvu prefixu hlafiny noveho stavu
  (setenv "GlobalnaPrefixHladinySeparator" "-")
)

(if (= (getenv "GlobalnaBlocksType") nil)
  ;nastavenie typu vkladaných blokov
  (setenv "GlobalnaBlocksType" "JTmenu")
)

(if (= (getenv "GlobalnaRebarType") nil)
  ;nastavenie modu pre vystuzovanie
  (setenv "GlobalnaRebarType" "Layer")
)

(if (= (getenv "GlobalnaRebarLegth") nil)
  ;nastavenie modu pre dlzku vystuze
  (setenv "GlobalnaRebarLegth" "Os")
)

(if (= (getenv "GlobalnaBlocksScale") nil)
  ;nastavenie mierky vkladenych blokov
  (setenv "GlobalnaBlocksScale" "50")
)

(if (= (getenv "GlobalnaSignBlocksScale") nil)
  ;nastavenie mierky nvkladanych blokov dopravneho znacenia
  (setenv "GlobalnaSignBlocksScale" "1000")
)

(if (= (getenv "GlobalnaBlocksLanguage") nil)
  ;nastavenie jazyku vkladanych blokov
  (setenv "GlobalnaBlocksLanguage" "SVK")
)

;;----------------------------------------------------------------------;;
;;           Uvitacia hlaska pri nacitany programu JTmenu               ;;
;;----------------------------------------------------------------------;;
;nastavenie premennej pre urcenie tvaru formatu cislovania
(setq FormatCislaVykresu (if (= (getenv "GlobalnyFormatCislaVykresu") "0") (setq FormatCislaVykresu "01")(setq FormatCislaVykresu "001")))

;nacitanie verzie programu
(load "JTmenu_version" "\nVerzia nenacitana!")

;nacitanie statusbaru
(command "modemacro" "Layer prefix: $(getenv,GlobalnaPrefixHladiny) | Mode: $(getenv,GlobalnaBlocksType) | Symbols: $(getenv,GlobalnaHladinaBlokov) | Rebar: $(getenv,GlobalnaRebarType)+$(getenv,GlobalnaRebarLegth) | Signs: $(getenv,GlobalnaSignBlocksScale)")

;vypisanie statusu o stave globalnych premenych
(princ
  (strcat
    "\n**********************************************"
    "\nJTmenu | " (JTmenuVersion) " | Jakub Tomecko | "
    (menucmd "m=$(edtime,0,yyyy)")
    "\n**********************************************"
    "\nNastavena hladina " (getenv "GlobalnaHladinaBlokov") " pre vkladane bloky!"
    "\nNastavily ste typ " (getenv "GlobalnaBlocksType") " pre vkladane bloky!"
    "\nNastavily ste mod pre vystuzovanie na: " (getenv "GlobalnaRebarType") "!"
    "\nNastavily ste mod pre dlzku vystuze na: " (getenv "GlobalnaRebarLegth") "!"
    "\nNastavena mierka je 1:" (getenv "GlobalnaBlocksScale") " pre vkladane bloky!"
    "\nNastavena mierka je 1:" (getenv "GlobalnaSignBlocksScale") " pre vkladane bloky dopravneho znacenia!"
    "\nNastaveny jazyk pre vkladane bloky je: " (getenv "GlobalnaBlocksLanguage") "!"
    "\nNastaveny mod " (getenv "GlobalnaKotyDIMSCALEset") " pre generovane koty!"
    "\nDimScale je nastaveny na hodnotu " (rtos (getvar "dimscale") 2 0) "!"
    "\nFormat cislovania vykresu je nastaveny na: " FormatCislaVykresu "."
    "\nMeno tagu vyhotovil pre rozpisku je nastavene na: " (getenv "GlobalneVyhotovilVykres") "."
    "\nPrexif nazvu hladiny je nastavene na: " (getenv "GlobalnaPrefixHladiny") "."
    "\nNastavily ste rozdelovac hladiny na: " (getenv "GlobalnaPrefixHladinySeparator") "."
    "\n**********************************************"
  )
) 
(princ)

;;----------------------------------------------------------------------;;
;;                             End of File                              ;;
;;----------------------------------------------------------------------;;
;; Poznamka: ponuka na (rucny) import .xtp/.xpg paliet dopravneho
;; znacenia uz nie je tu - spusta sa az pri zapnuti prislusneho panelu
;; (JTTrafficSigns / JTTrafficSignsExisting v Traffic_signs*.lsp), nie
;; pri kazdom starte AutoCADu. Zdielana logika je v JT:OfferToolPaletteImport
;; (JTmenu_lib.lsp). Manualne znovuspustenie: JTToolPaletteImportInfo.
